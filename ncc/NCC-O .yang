// ===================================================================
//
//		N C C   F E A T U R E   S E T S
//
// 	This file is a collection of separate modules.  
//		When they're distributed, each module will be a separate file
//		that device schemas can import as needed. 
//
//		Feature-set module names begin with "fs"  
//
// ===================================================================
	
module fsReceiverMonitoring {
	description 
	"
		Receiver monitoring feature set
	"
	// -Header---------------------------------------------------------
	
	yang-version	1.1;
	namespace 		urn:nca:ncc;
	belongs-to		ncc-o;
	prefix 				ncc;
	revision 			2021-07-27	{
		description 
		"
			This version defines the general receiver monitoring feature set,
			and especially the IS-05 receiver monitoring class.
		"
	}

	reference			"RFC 7950 - YANG 1.1";
	reference			"RFC 6095 - Extending YANG with Language Abstractions";

	// IETF extension that allows complex types & inheritance 
	import				ietf-complex-types {prefix ct;}
	
	// NCA extension to handle various NCA-specific constructs 
	import 				nca-extensions {prefix nc;}
	
	// ----------------------------------------------------------------

	enumeration ncaConnectionStatus {
		enum Undefined								{value:0;}	// This is the value when there's no receiver		
		enum Disconnected						{value:1;}
		enum Connecting							{value:2;}
		enum Connected								{value:3;}
		enum ConnectionError					{value:4;}
	}
	
	enumeration ncaPayloadStatus {
		enum Undefined								{value:0;}	// This is the value when there's no connection
		enum NoPayload								{value:1;}
		enum PayloadOK								{value:2;}
		enum PayloadFormatUnsupported	{value:3;}
		enum PayloadError						{value:4;}
	}
	
	ct:complex-type ncaReceiverMonitor {
		ct:extends 	ncaAgent;
		ct:abstract	true;
		description
		"	
			Abstract receiver monitoring agent.
			Specific kinds of receiver monitors inherit from this class.
		"
		
		cx:class-id "1,1.4.1"					// root<-agent<-this
		leaf connectionStatus					{type:ncaConnectionStatus;	cx:element-id "3p1";}
		leaf connectionStatusMessage		{type:ncaString;					cx:element-id "3p2";}
		leaf	payloadStatus						{type:ncaPayloadStatus;		cx:element-id "3p3";}
		leaf payloadStatusMessage			{type:ncaString;					cx:element-id "3p4";}
	
		action GetStatus {
			cx:element-id "3m1";
			output {
				MethodStatus					{type:ncaMethodStatus;}
				ConnectionStatus				{type:ncaConnectionStatus;}
				PayloadStatus					{type:ncaPayloadStatus;}
			}
		}
		action GetConnectionStatusMessage{
			cx:element-id "3m2";
			output {
				MethodStatus					{type:ncaMethodStatus;}
				Message							{type:ncaString;}
			}
		}
		action GetPayloadStatusMessage{
			cx:element-id "3m3";
			output {
				MethodStatus					{type:ncaMethodStatus;}
				Message							{type:ncaString;}
			}
		}
		//		NOTIFICATIONS:
		//
		// 	This method inherits the property-changed event from OcaRoot.
		//		That event is the primary means by which controllers will learn
		//		of receiver status changes.  The Get(...) methods listed above
		//		should not be used for polling receiver status. Instead, controllers
		//		should subscribe to the property-changed event.
	}
	 
	 ct:complex-type ncaIS05ReceiverMonitor {
		ct:extends 	ncaReceiverMonitor;
		description
		"
			NMOS IS-05 receiver monitor.
			Inherits from abstract class ncaReceiverMonitor.
		"
		
		cx:class-id							"1,1.4.1.1"				// root<-agent<-receiverMonitor<-this
		leaf	receiverUUID				{type:ncaUUID;	cx:element-id "4p1";}
		
		action GetReceiverUUID {
			cx:element-id "4m1";
			output {
				MethodStatus				{type:ncaMethodStatus;}
				UUID								{type:ncaUUID}
			}
		}
		action SetReceiverUUID {
			cx:element-id "4m2";
			output {
				MethodStatus				{type:ncaMethodStatus;}
			}
			Input {
				UUID								{type:ncaUUID}
			}
		}
	}
}
